;AM 141114-052038
(defun c:isoblock(/ ss1)
	(setq ss1 (SSGET "_X" '((0 . "INSERT"))))
	(command "isolateobjects" ss1 "")
)
(defun c:isohatch(/ ss1)
	(setq ss1 (SSGET "_X" '((0 . "HATCH"))))
	(command "isolateobjects" ss1 "")
)
(defun c:selhatch(/ ss1)
	(setq ss1 (SSGET "_X" '((0 . "HATCH"))))
	(sssetfirst nil ss1)
)
(defun c:isowipe (/ ss1)
	(setvar "pickstyle" 0)
	(setq ss1 (ssget "x" '((0 . "wipeout"))))
	(command "._isolateobjects" ss1 "")
)
(defun c:selwipe(/ ss1)
	(setq ss1 (ssget "x" '((0 . "wipeout"))))
	(sssetfirst nil ss1)
)
(defun c:seldim(/ ss1)
	(setq ss1 (ssget "x" '((0 . "DIM*"))))
	(sssetfirst nil ss1)
)
(defun c:selxline(/ ss1)
	(setq ss1 (ssget "x" '((0 . "XLINE*"))))
	(sssetfirst nil ss1)
)


;(ssget "x" (list (cons 0 "DIM*")))
