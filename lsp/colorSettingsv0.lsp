(defun c:COLOR_SETTINGS ()
	(command "_layer" "color" "30" "*A-ANNO*" "")
	(command "_layer" "color" "30" "*Dimension*" "")
	(command "_layer" "color" "1" "*A-05*,*A-DOOR*,*A-FLOR*,*A-WALL-FRMG*" "")
	(command "_layer" "color" "1" "*A-RCP*,*A-SITE*,*A-STRUCT*,*A-UTIL*" "")
	(command "_layer" "color" "40" "*A-13*,*A-EQPM*,*A-FLOR-CASE*,*A-FLOR-FURN*,*A-FLOR-HVAC*,*A-ROOF*" "")
	(command "_layer" "color" "104" "*A-18*" "")
	(command "_layer" "color" "132" "*A-25*,*A-GLAZ*,*A-WALL-PRHT*" "")
	(command "_layer" "color" "150" "*A-35*,*A-WALL-FULL*" "")
	(command "_layer" "color" "190" "*A-50*" "")
	(command "_layer" "color" "8" "*WIPE*,*A-WALL-PATT*,*A-FLOR-PATT*,*A-ROOF-PATT*" "")
	(command "_layer" "color" "8" "*A-GRID*, *xref*" "")
	(command "_layer" "color" "155" "*A-GRID-PLAN-NS*" "")
	(command "_layer" "color" "75" "*A-GRID-PLAN-EW*" "")
	(command "_layer" "color" "6" "*NonPlot*,*Viewport*" "")
	(command "_layer" "color" "truecolor" "255,255,255" "*WIPE*" "")
	;demo
	(command "_layer" "color" "200" "*A-DEMO" "")
	(command "_layer" "color" "180" "*A-DEMO-WALL-FULL*" "")
	(command "_layer" "color" "202" "*A-DEMO-GLAZ*" "")
	(command "_layer" "color" "190" "*A-DEMO-DOOR*" "")
	(command "_layer" "color" "190" "*A-DEMO-WALL-PRHT*" "")
	(command "_layer" "color" "192" "*A-DEMO-FLOR-STRS*" "")
	(command "_layer" "color" "192" "*A-DEMO-EQPM*" "")
	(command "_layer" "color" "180" "*A-DEMO-PATT*, *A-DEMO-WALL-PATT*" "")
	;existing
	(command "_layer" "color" "181" "*A-EXST*" "")
	(command "_layer" "color" "153" "*A-EXST-WALL-FULL*" "")
	(command "_layer" "color" "165" "*A-EXST-DOOR*, *A-EXST-GLAZ*, *A-EXST-WALL-PRHT*" "")
	(command "_layer" "color" "21" "*A-EXST-FLOR-STRS*" "")
	(command "_layer" "color" "43" "*A-EXST-EQPM*" "")
	(command "_layer" "color" "31" "*A-EXST-FLOR-OVHD*" "")
	(command "_layer" "color" "11" "*A-EXST-FLOR-EDGE*" "")
	(command "_layer" "color" "9" "*A-EXST-WALL-PATT*" "")
	;override previous steps in specific cases
	(command "_layer" "color" "62" "*A-STRUCT-COL*,*A-COL*" "")
)
; (defun c:COLOR_SETTINGS ()
; (command "_layer" "color" "5" "*A-DEMO" "")
; (command "_layer" "color" "191" "*A-DEMO-WALL-PATT*" "")
; (command "_layer" "color" "191" "*A-DEMO-PATT*" "")
; (command "_layer" "color" "1" "*A-ANNO*" "")
; (command "_layer" "color" "1" "*A-05*" "")
; (command "_layer" "color" "40" "*A-13*" "")
; (command "_layer" "color" "72" "*A-18*" "")
; (command "_layer" "color" "140" "*A-25*" "")
; (command "_layer" "color" "Blue" "*A-35*" "")
; (command "_layer" "color" "182" "*A-50*" "")
; (command "_layer" "color" "1" "*A-DOOR" "")
; )
