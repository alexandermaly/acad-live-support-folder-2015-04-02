;load a bunch of lisps
(princ "loading lisps\n")
(load "lsp/layer_list.lisp")
(load "lsp/LayerStates-1_2.fas" "failed loading layerstates")
(load "lsp/sel.lsp" "failed loading SEL")
(load "lsp/plan-demo-settings-v0.lsp" "failed loading demo settings")
(load "lsp/plan-wall-settings-v0.lsp" "failed loading wallSettingsv0")
(load "lsp/plan-rcp-settings-v0.lsp" "failed loading rcpSettingsv0")
(load "lsp/plan-ffe-settings-v0.lsp" "failed loading plan-settings-v0")
(load "lsp/plan-finish-settings-v0.lsp" "failed loading plan-finish-settings-v0")
(load "lsp/plan-power-settings-v0.lsp" "failed loading plan-power-settings-v0")
(load "lsp/colorSettingsv0.lsp" "failed loading colorSettingsv0")
(load "lsp/exstRenamev0.lsp" "failed loading exstRenamev0")
(load "lsp/updblkcl.lsp" "failed loading updblkcl.lsp")
(load "lsp/updblkclall.lsp" "failed loading updblkclall.lsp")
(load "lsp/isolate.lsp" "failed loading isolate.lsp")
(load "lsp/rotatemultiple.lsp" "failed loading rotatemultiple.lsp")
(load "lsp/scaleall.lsp" "failed loading scaleall.lsp")
(load "lsp/mirrorall.lsp" "failed loading mirrorall.lsp")

(princ "\nlisps loaded \n")
(defun c:note_settings()
	(command "_layer" "lweight" "0.13" "*A-ANNO-NOTE*" "")
)
(defun c:setblack()
	(command "_layer" "color" "7" "*" "")
	)
(defun c:setwipe()
	(command "_layer" "color" "truecolor" "255,255,255" "*WIPE*" "")
	)
	
(defun c:nonplot_settings ()
	(command "_layer" "on" "*_Viewport_Crop*,*Viewport*" "")
	(command "_layer" "plot" "no" "*NonPlot*,*_Viewport_Crop*,*Viewport*" "")
	(command "_layer" "thaw" "*NonPlot*" "")
;	(command "_layer" "thaw" "*24x36|NonPlot*" "")
;	(command "_layer" "thaw" "NonPlot" "")
	(command "_layer" "color" "6" "*NonPlot*,*_Viewport_Crop*,*Viewport*" "")
	(command "_layer" "pstyle" "Normal" "*NonPlot*,*Viewport*" "")

)
(defun c:gr1()
	(command "_layer" "thaw" "*A-GRID-PLAN-*" "")
	)
(defun c:gr0()
	(command "_layer" "freeze" "*A-GRID-PLAN-*" "")
	)
(defun c:tbe()
	(command "bedit" "Titleblock-Sheetblock")
	)
(defun c:stb_settings () 
	(command "_layer" "pstyle" "Solid" "*" "")
	(command "_layer" "pstyle" "Normal" "*NonPlot*,*Viewport*" "")
	(command "_layer" "pstyle" "Normal" "*WIPE*" "")
)
(defun c:ssr ()
	(setq ss1 (ssget "P"))
	(sssetfirst nil ss1)
	(prin1)
)
(defun c:frr () (command "draworder" "front"))
(defun c:baa () (command "draworder" "back"))
(defun c:xra () (command "xref" "reload" "*"))
(defun c:xru () (command "xref" "unload" "*"))
(defun c:xr0 () (command "_layer" "freeze" "*xref*" ""))
(defun c:xr1 () (command "_layer" "thaw" "*xref*" ""))
(defun c:tda () (command "_layer" "thaw" "*Titleblock-Dynamic*" ""))
(defun c:tn0 () (command "_layer" "freeze" "*Titleblock-NorthArrow*" ""))
(defun c:tn1 () (command "_layer" "thaw" "*Titleblock-NorthArrow*" ""))
(defun c:nn0 () (command "_layer" "freeze" "*NonPlot*,*NPLT*" ""))
(defun c:nn1 () (command "_layer" "thaw" "*NonPlot*,*NPLT*" ""))
(defun c:vv0 () (command "_layer" "freeze" "*Viewport*" ""))
(defun c:vv1 () (command "_layer" "thaw" "*Viewport*" ""))

(defun c:nnv1 () (command "_vplayer" "thaw" "*NonPlot*" "Current" ""))
(defun c:dd0 () (command "_layer" "freeze" "*ANNO-DIM*,*Anno-Dim*,*Dimension*" ""))
(defun c:dd1 () (command "_layer" "thaw" "*ANNO-DIM*,*Anno-Dim*,*Dimension*" ""))
(defun c:ff0 () (command "_layer" "freeze" "*FURN*" ""))
(defun c:ff1 () (command "_layer" "thaw" "*FURN*" ""))
(defun c:ee0 () (command "_layer" "freeze" "*exst*" ""))
(defun c:ee1 () (command "_layer" "thaw" "*exst*" ""))
(defun c:cl0 () (command "_layer" "freeze" "*CLNG*" ""))
(defun c:cl1 () (command "_layer" "thaw" "*CLNG*" ""))

(defun c:wh0 () (command "_layer" "freeze" "*WALL-HEAD*,*FLOR-OVHD*" ""))
(defun c:wh1 () (command "_layer" "thaw" "*WALL-HEAD*,*FLOR-OVHD*" ""))
(defun c:ovh () (command "_layer" "ltype" "HIDDEN2" "*WALL-HEAD*,*FLOR-OVHD*" ""))

(defun C:LGD () (command ".LENGTHEN" "DYnamic") (princ)) ;Extend or Trim Item to Point
(defun C:LIMFIT () (command ".LIMITS" (getvar "EXTMIN") (getvar "EXTMAX")) (princ)) ;Reset Limits

(defun c:ww ()
	(if (= (getvar "LWDISPLAY") 1) (setvar "LWDISPLAY" 0) (setvar "LWDISPLAY" 1))
)
(defun c:demoOff () (command "_layer" "freeze" "*A-DEMO*" "") (princ "demo was frozen!") )
(defun c:demoOn () (command "_layer" "thaw" "*A-DEMO*" "") (princ "demo was thawed!") )

(defun c:npAllOff () 
	(command "_layer" "freeze" "*NonPlot*" "")
	(princ "NonPlot Off!")
)
(defun c:nplOn () 
	(command "_layer" "thaw" "NonPlot" "")
	(princ "Nonplot Local On!")
)
(defun c:npAllOn () 
	(command "_layer" "thaw" "*NonPlot*" "")
	(princ "Nonplot Local On!")
)
(defun c:areaOff () 
	(command "_layer" "freeze" "*AREA*,*Area*" "")
	(princ "AREAOFF!")
)
(defun c:saveclose () 
	(command "._save" "")
	(princ (car(layoutlist)))
	(command "._close" "")
)
(defun c:qsaveclose () 
	(command "_qsave" "")
	(princ (car(layoutlist)))
	(command "._close" "")
)
(defun c:REL() (load "startup.lsp") (prin1))
;(defun c:BYL() (command "._chprop" (ssget) "Color" "ByLayer" "Lineweight" "ByLayer" "LineType" "ByLayer" "") )
(defun c:bb (/ ss1)
  (setq ss1 (ssget))
  (command "change" ss1 "" "p" "Color" "ByLayer" "LWeight" "ByLayer" "Ltype" "ByLayer" "PlotStyle" "ByLayer" "")
  )
(defun c:nnn (/ ss1)
  (setq ss1 (ssget))
  (command "change" ss1 "" "p" "Layer" "NonPlot" "")
)
(defun c:ddd (/ ss1)
  (setq ss1 (ssget))
  (command "change" ss1 "" "p" "Layer" "Dimension" "")
)
(defun c:ttt (/ ss1)
  (setq ss1 (ssget))
  (command "change" ss1 "" "p" "Layer" "Titleblock" "")
)
(defun c:dimo1 (/ ss1)
  (setq ss1 (ssget))
  (command "DIMOVERRIDE" "C" ss1 "")
)


; (defun c:isoblocks(/ ss1)
; 	(setq ss1 (SSGET "_X" '((0 . "INSERT"))))
; 	(command "isolateobjects" ss1 "")
; )
; (defun c:isohatch(/ ss1)
; 	(setq ss1 (SSGET "_X" '((0 . "HATCH"))))
; 	(command "isolateobjects" ss1 "")
; )
; (defun c:selhatch(/ ss1)
; 	(setq ss1 (SSGET "_X" '((0 . "HATCH"))))
; 	(sssetfirst nil ss1)
; )
; (defun c:isowipe (/ b)
; 	(setvar "pickstyle" 0)
; 	(setq b (ssget "x" '((0 . "wipeout"))))
; 	(command "._isolateobjects" b "")
; )
; ;(defun c:hasso(/ ss1)
; 	(setq ss1 (ssget))
; 	(setq ss2 (ssget))
; 	(command "_hatchedit" ss1 "associate" ss2 "")
; )

(defun c:glasshatch(/ ss1)
	(setq ss1 (ssget))
	(command "_hatchedit" ss1 "layer" "A-WALL-PATT" "")
	(command "_hatchedit" ss1 "color" "ByLayer" "" "")
	(command "_hatchedit" ss1 "properties" "GLASS" "96" "45")
)

(defun c:restr(/ ss1)
	(command "stretch" (ssget) "" "Displacement" "")
)

(defun c:bba ()
  (setq setOfAll1 (ssget "x"));
  (command "change" setOfAll1 "" "p" "Color" "ByLayer" "LWeight" "ByLayer" "Ltype" "ByLayer" "PlotStyle" "ByLayer" "")
  )

(defun c:pbAll()
 (command "purge" "B" "*" "N")
)

(defun c:ss()
	(if (= (getvar "TILEMODE") 1) (setvar "TILEMODE" 0) (setvar "TILEMODE" 1))
)

(defun c:cc () (command "._copybase" "0,0" (ssget) ""))
(princ "copy origin loaded\n")
(defun c:dd () (command "._pasteclip" "0,0"))
(princ "paste origin loaded\n")
(defun c:xrr ()
	(command "._xref" "pathType" "*" "relative")
	(princ "RELATIVE!")
)
(defun c:xrefstoxref ( / a b c d e )
    (while (setq a (tblnext "BLOCK" (null a)))
        (if (= 4 (logand 4 (cdr (assoc 70 a))))
            (setq b (cons "," (cons (cdr (assoc 2 a)) b)))
        )
    )
    (if (and b (setq c (ssget "_X" (list '(0 . "INSERT") (cons 2 (apply 'strcat (cdr b)))))))
        (repeat (setq d (sslength c))
            (setq e (entget (ssname c (setq d (1- d)))))
            (entmod (subst (cons 8 "xref") (assoc 8 e) e))
        )
    )
    (princ)
)

(defun c:exall(/ bSet)
  (setvar "qaflags" 1)
  (while(setq bSet(ssget "_X" '((0 . "INSERT"))))
    (command "_.explode" bSet "")
    ); end while
  (repeat 3(command "-purge" "all" "" "n"))
  (setvar "qaflags" 0)
(princ)
); end of c:exall
(defun c:bss(/ s)
    	(setvar "cmdecho" 0)
		(command "_bedit");
		(setq setOfAll1 (ssget "_X"));
		(c:bylall)
		(command "._bsave")
		(command "._bclose")
		(setvar "cmdecho" 1)
		;(command "._hideobjects" sscurrent);
		
);
(defun c:bsc(/ s)
    	;(setvar "cmdecho" 0)
		(command "._bsave")
		(command "._bclose")
		;(setvar "cmdecho" 1)
		;(command "._hideobjects" sscurrent);
		
);
(defun c:zs()
	(setvar "cmdecho" 0)
	(command "_model");
	(princ "modeling!!\n");
	(setq setOfAll1 (ssget "x"));
	(princ setOfAll1)(princ "\n");
	(command "._copybase" "0,0" setOfAll1 "")(princ "modelspace copied\n");
	(setvar "cmdecho" 1);
	(command "_zoom" "a")
);
(defun c:rs()
	(setvar "cmdecho" 0)
	(setvar 'ctab (car(layoutlist)))
	(setq setOfAll2 (ssget "x"))
	(command "._copybase" "0,0" setOfAll2 "")(princ "paperspace1 copied\n");
	(princ (car(layoutlist)))
	(setvar "cmdecho" 1)
	(command "_zoom" "a")
)
(defun c:zd()
	(setvar "cmdecho" 0)
	(command "_model");
	(command "._pasteclip" "0,0");
	(princ "pasted model")
	(setvar "cmdecho" 1);
	(command "_zoom" "a")
);
(defun c:rd()
	(setvar "cmdecho" 0)
	(setvar 'ctab (car(layoutlist)))
	(command "._pasteclip" "0,0")
	(setvar "cmdecho" 1);
	(princ "pasted paper1")
	(command "_zoom" "a")
)
(defun c:floorPatt()
	(setq linelist '(("DOT10" . "acad2.lin")))
	(princ "patt will be ")(princ linelist)
	(foreach lin linelist
		(if (tblsearch "LTYPE" (car lin))
			(command "_linetype" "_load" (car lin) (cdr lin) "_yes" "")
			(command "-linetype" "_load" (car lin) (cdr lin) "")
		)
	)
	(command "_layer" "ltype" "DOT10" "*A-FLOR-PATT*" "")
)
(defun c:isowipe (/ b)
 (setvar "pickstyle" 0)
 (setq b (ssget "x" '((0 . "wipeout"))))
 (command "._isolateobjects" b "")
)
; (if s::startup
;  (setq s::startup (append s::startup (command "WSCURRENT" "MyWorkspace")))
;  (defun s::startup () (command "WSCURRENT" "MyWorkspace"))
; )
(command "POLARANG" "15")
; (c:DEMOPLAN_SETTINGS)
; (princ "DPWIN")
; (c:RCP_SETTINGS)
; (princ "RCPWIN")
; (c:EXST_RENAME)
; ; (princ "exst!")
; (c:demoOff)
;(c:nonplot_settings)
; (c:WALL_SETTINGS)
;(c:xrr)
;(c:nonplotOff)
;(c:bylall)
;(c:stb_settings)
; (command "LAYTHW")
; (command "LAYON")
; (command "_layer" "freeze" "*A-GRID*" "")
;(command "_layer" "thaw" "*A-GRID-PLAN-*" "")
; (command "_layer" "thaw" "*A-GRID-ELEV*" "")
;(setvar 'ctab (car(layoutlist)))
;(command "_mview" "fit" "")
;(command "_layer" "freeze" "*NorthArrow*" "")
;(c:por)
;(c:note_settings)
;(c:nonplot_settings)
;(c:saveclose)
;set NOTE black override
;(setvar 'ctab (car(layoutlist)))
;(command "TILEMODE" "1")
;(c:c1)
;(command "zoom" "extents" "")
;(c:saveclose)
(DEFUN C:RRT ()
 (command "-layout" "rename" "" (getvar "dwgname"))
 (princ)
)
(defun c:newstandard()
	(c:xrr)
	(c:allcolorblack)
	(c:nonplot_settings)
	(command "_layer" "color" "250" "*A-ANNO*" "")
	(c:stb_settings)
	(c:bba);bylayerall
	(c:RRT);rename layout
	;(c:xrefstoxref)
)
;(load "lsp/xref_repath.lsp")
;(setvar "TILEMODE" 1)
;(command "_zoom" "a")
;(c:color_settings)
;(command "_layer" "color" "250" "*A-ANNO*" "")
;(c:xrefstoxref)
;(c:newstandard)
;(c:saveclose)
(defun c:tbinit()
	(setvar "TILEMODE" 0)
	(c:dd)
	(c:tda)
	(c:tn1)
;(c:color_settings)
)
;(c:tbinit())
;(command "-purge" "all" "" "n")
;(c:nonplot_settings)
;(c:wh1)
(defun c:enlargedplan_nodim()
	(c:ovh)
	(c:wh1)
	(command "LTSCALE" "0.5")
	(c:seldim)
	(c:nnn)
	(c:stb_settings)
	)
;(c:nonplot_settings)
;(c:stb_settings)
;(c:qsaveclose)
